module ietf-te-topology {
  yang-version 1;
  namespace "urn:ietf:params:xml:ns:yang:ietf-te-topology";
  // replace with IANA namespace when assigned
  
  prefix "tet";

  import ietf-yang-types { 
    prefix "yang"; 
  }

  import ietf-inet-types {
    prefix "inet";
  }

  import ietf-interfaces {
    prefix "if";
  }

  import ietf-te-types {
    prefix "te-types";
  }

  organization "TBD";
  contact "TBD";
  description "TE topology model";
  
  revision "2015-07-02" {
    description "Initial revision";
    reference "TBD";
  }

  /*
   * Features
   */

  feature te-topology-hierarchy {
    description
      "This feature indicates that the system allows underlay
      and/or overlay TE topology hierarchy.";
  }

  feature te-performance-metric {
    description
      "This feature indicates that the system supports
      TE performance metric defined in
      draft-ietf-ospf-te-metric-extensions.";
  }

  feature configuration-schedule {
    description
      "This feature indicates that the system supports 
      configuration scheduling.";
  }

  feature template {
    description
      "This feature indicates that the system supports 
      template configuration.";
  }

  /*
   * Typedefs
   */

typedef te-recovery-status {
    type enumeration {
      enum normal {
        description
          "Both the recovery and working spans are fully
          allocated and active, data traffic is being
          transported over (or selected from) the working
          span, and no trigger events are reported.";
      }
      enum recovery-started {
        description
          "The recovery action has been started, but not completed.";
      }
      enum recovery-succeeded {
        description
          "The recovery action has succeeded. The working span has
          reported a failure/degrade condition and the user traffic
          is being transported (or selected) on the recovery span.";
      }
      enum recovery-failed {
        description
          "The recovery action has failed.";
      }
      enum reversion-started {
        description
          "The reversion has started.";
      }
      enum reversion-failed {
        description
          "The reversion has failed.";
      }
      enum recovery-unavailable {
        description
          "The recovery is unavailable -- either as a result of an
          operator Lockout command or a failure condition detected
          on the recovery span.";
      }
      enum recovery-admin {
        description
          "The operator has issued a command switching the user
          traffic to the recovery span.";
      }
      enum wait-to-restore {
        description
          "The recovery domain is recovering from a failuer/degrade
          condition on the working span that is being controlled by
          the Wait-to-Restore (WTR) timer.";
      }
      enum primary-active {
        description
          "Primary is active.";
      }
    }
    description
      "Defines the status of a recovery action.";
    reference
      "RFC4427: Recovery (Protection and Restoration) Terminology
      for Generalized Multi-Protocol Label Switching (GMPLS).
      RFC6378: MPLS Transport Profile (MPLS-TP) Linear Protection";
  }
  typedef te-admin-status {
    type enumeration {
      enum up {
        description
          "Enabled.";
      }
      enum down {
        description
          "Disabled.";
      }
      enum testing {
        description
          "In some test mode.";
      }
      enum preparing-maintenance {
        description
          "Resource is disabled in the control plane to prepare for
          graceful shutdown for maintenance purposes.";
        reference
          "RFC5817: Graceful Shutdown in MPLS and Generalized MPLS
          Traffic Engineering Networks";
      }
      enum maintenance {
        description
          "Resource is disabled in the data plane for maintenance
          purposes.";
      }
    }
    description
      "Defines a type representing the administrative status of 
      a TE resource.";
  }

  typedef te-global-id {
    type uint32;
    description
      "An identifier to uniquely identify an operator, which can be
      either a provider or a client.
      The definition of this type is taken from RFC6370 and RFC503.
      This attribute type is used solely to provide a globally
      unique context for TE topologies.";
  }

  typedef te-topology-id {
    type string {
      pattern '/?([a-zA-Z0-9\-_.]+)(/[a-zA-Z0-9\-_.]+)*';
    }
    description
      "An identifier for a topology.";
  }

  typedef te-template-name {
    type string {
      pattern '/?([a-zA-Z0-9\-_.]+)(/[a-zA-Z0-9\-_.]+)*';
    }
    description
      "A type for the name of a TE node template or TE link
      template.";
  }

  typedef te-node-id {
    type inet:ip-address;
    description
      "An identifier for a node in a topology.
       The identifier is represented as an IPv4 or IPv6 address.
       The identifier SHOULD be chosen such that the same node in a
       real network topology will always be identified through the
       same identifier, even if the model is instantiated in separate
       datastores. An implementation MAY choose to capture semantics
       in the identifier, for example to indicate the type of node
       and/or the type of topology that the node is a part of.";
  }

  typedef te-link-id {
    type union {
      type uint32;          // Unnumbered
      type inet:ip-address; // IPv4 or IPv6 address
    }
    description
      "An identifier for a TE link on a node.
       The identifier may be opaque.
       The identifier SHOULD be chosen such that the same TP in a
       real network topology will always be identified through the
       same identifier, even if the model is instantiated in separate
       datastores. An implementation MAY choose to capture semantics
       in the identifier, for example to indicate the type of TP
       and/or the type of node and topology that the TP is a part
       of.";
  }
  
  typedef te-topology-event-type {
    type enumeration {
      enum "add" {
        value 0;
        description 
          "A TE node or te-link has
          been added";
      }
      enum "remove" {
        value 1;
        description 
          "A TE node or te-link has
          been removed";
      }
      enum "update" {
        value 2;
        description 
          "A TE node or te-link has
          been updated";
      }
    }
    description "TE  Event type for notifications";
  } // te-topology-event-type

  typedef performance-metric-normality {
    type enumeration {
      enum "unknown" {        
        value 0;
        description
          "Unknown";
      }
      enum "normal" {        
        value 1;
        description
          "Normal";
      }
      enum "abnormal" {        
        value 2;
        description
          "Abnormal. The anomalous bit is set.";
      }
    }
    description
      "Indicates whether a performance metric is normal, abnormal, or
      unknown.";
  }

  /*
   * Identities
   */

  identity flag-identity {
    description "Base type for flags";
  }

  identity undefined-flag {
    base "flag-identity";
    description "Undefined flag";
  }
  
  typedef flag-type {
    type identityref {
      base "flag-identity";
    }
    description "Type for flags";
  }

  /*
   * Groupings
   */

  grouping topo-ref {
    description
      "Grouping for an absolute reference to a topology instance.";
    leaf provider-id-ref {
      type leafref {
        path "/tet:te-topologies/tet:topology/tet:provider-id";
      }
      description
        "An absolute reference to a provider-id.";
    }
    leaf client-id-ref {
      type leafref {
        path "/tet:te-topologies/tet:topology/tet:client-id";
      }
      description
        "An absolute reference to a client-id.";
    }
    leaf topology-id-ref {
      type leafref {
        path "/tet:te-topologies/tet:topology/tet:te-topology-id";
      }
      description
        "An absolute reference to a te-topology-id.";
    }
  } // topo-ref

  grouping link-ref {
    description
      "Grouping for an absolute reference to a link instance.";
    uses topo-ref;
    leaf source-te-node-id-ref {
      type leafref {
        path "/tet:te-topologies/tet:topology"
          +"[tet:provider-id = current()/../provider-id-ref]"
          +"[tet:client-id = current()/../client-id-ref]"
          +"[tet:te-topology-id = current()/../topology-id-ref]"
          +"/tet:link/tet:source-te-node-id";
      }
      description
        "An absolute reference to a link instance.";
    }
    leaf source-te-link-id-ref {
      type leafref {
        path "/tet:te-topologies/tet:topology"
          +"[tet:provider-id = current()/../provider-id-ref]"
          +"[tet:client-id = current()/../client-id-ref]"
          +"[tet:te-topology-id = current()/../topology-id-ref]"
          +"/tet:link/tet:source-te-link-id";
      }
      description
        "An absolute reference to a link instance.";
    }
    leaf dest-te-node-id-ref {
      type leafref {
        path "/tet:te-topologies/tet:topology"
          +"[tet:provider-id = current()/../provider-id-ref]"
          +"[tet:client-id = current()/../client-id-ref]"
          +"[tet:te-topology-id = current()/../topology-id-ref]"
          +"/tet:link/tet:dest-te-node-id";
      }
      description
        "An absolute reference to a link instance.";
    }
    leaf dest-te-link-id-ref {
      type leafref {
        path "/tet:te-topologies/tet:topology"
          +"[tet:provider-id = current()/../provider-id-ref]"
          +"[tet:client-id = current()/../client-id-ref]"
          +"[tet:te-topology-id = current()/../topology-id-ref]"
          +"/tet:link/tet:dest-te-link-id";
      }
      description
        "An absolute reference to a link instance.";
    }
  } // link-ref

  grouping node-ref {
    description
      "Grouping for an absolute reference to a node instance.";
    uses topo-ref;
    leaf node-ref {
      type leafref {
        path "/tet:te-topologies/tet:topology"
          +"[tet:provider-id = current()/../provider-id-ref]"
          +"[tet:client-id = current()/../client-id-ref]"
          +"[tet:te-topology-id = current()/../topology-id-ref]"
          +"/tet:node/tet:te-node-id";
      }
      description
        "An absolute reference to a node instance.";
    }
  } // node-ref

  grouping link-end-ref {
    description
      "Grouping for an absolute reference to a TE link end, which is
      the local representation of a TE link on a node.";
    uses node-ref;
    leaf link-end-ref {
      type leafref {
        path "/tet:te-topologies/tet:topology"
          +"[tet:provider-id = current()/../provider-id-ref]"
          +"[tet:client-id = current()/../client-id-ref]"
          +"[tet:te-topology-id = current()/../topology-id-ref]"
          +"/tet:node[tet:te-node-id = current()/../node-ref]"
          +"/tet:te-link/tet:te-link-id";
      }
      description
        "Grouping for an absolute reference to a TE link end.";
    }
  } // link-end-ref

  grouping te-topology-type {
    description
      "Identifies the TE topology type.";
    container te-topology {
      presence "indicates TE topology";
      description
        "Its presence identifies the TE topology type.";
    }
  } // te-topology-type
  
  grouping te-path-element {
    description
      "A group of attributes defining an element in a TE path
      such as TE node, TE link, TE atomic resource or label.";
    uses te-types:explicit-route-subobject;
  } // te-path-element
  
  grouping config-schedule-attributes {
    description
      "A list of schedules defining when a particular 
       configuration takes effect.";
    list schedules {
      if-feature configuration-schedule;
      key "schedule-id";
      description "A list of schedule elements.";
      
      leaf schedule-id {
        type uint32;
        description "Identifies the schedule element.";
      }
      leaf start {
        type yang:date-and-time;
        description "Start time.";
      }
      leaf schedule-duration {
        type string {
          pattern 
            'P(\d+Y)?(\d+M)?(\d+W)?(\d+D)?T(\d+H)?(\d+M)?(\d+S)?';
        }
        description "Schedule duration in ISO 8601 format.";
      }
      leaf repeat-interval {
        type string {
          pattern 
            'R\d*/P(\d+Y)?(\d+M)?(\d+W)?(\d+D)?T(\d+H)?(\d+M)?'
            + '(\d+S)?';
        }
        description "Repeat interval in ISO 8601 format.";
     }
    }
  } // config-schedule-attributes

  grouping information-source-attributes {
    description
      "The attributes identifying source that has provided the 
      related information, and the source credibility.";
    leaf information-source {
      type enumeration {
        enum "unknown" {
          description "The source is unknown";
        }
        enum "locally-configured" {
          description "Configured entity";
        }
        enum "ospfv2" {
          description "OSPFv2";
        }
        enum "ospfv3" {
          description "OSPFv3";
        }
        enum "isis" {
          description "ISIS";
        }
        enum "system-processed" {
          description "System processed entity.";
        }
        enum "other" {
          description "Other source";
        }
      }
      description 
        "Indicates the source of the information.";
    }
    container information-source-state {
      description
        "The container contains state attributes related to 
        the information source.";
      leaf credibility-preference {
        type uint16;
        description
          "The preference value to calculate the traffic 
          engineering database credibility value used for 
          tie-break selection between different 
          information-source values.
          Higher value is more preferable.";
      }      
      container topology {
        description 
          "When the information is processed by the system,
          the attributes in this container indicate which topology
          is used to process to generate the result information.";
        leaf provider-id-ref {
          type leafref {
            path "/tet:te-topologies/tet:topology/tet:provider-id";
          }
          description
            "A reference to a provider-id.";
        }
        leaf client-id-ref {
          type leafref {
            path "/tet:te-topologies/tet:topology/tet:client-id";
          }
          description
            "A reference to a client-id.";
        }
        leaf topology-id-ref {
          type leafref {
            path "/tet:te-topologies/tet:topology"
              +"/tet:te-topology-id";
          }
          description
            "A reference to a te-topology-id.";
        }
      } // topology
      leaf routing-instance {
        type string;
        description
          "When applicable, this is the name of a routing instance
            from which the information is learned.";
      } // routing-information
    }
  } // information-source-attributes

  grouping te-node-attributes {
    description "Node attributes in a TE topology.";
    container te-node-attributes {
      description "Node attributes in a TE topology.";
      uses config-schedule-attributes;
      leaf name {
        type inet:domain-name;
        description "Node name.";
      }
      leaf-list signaling-address {
        type inet:ip-address;
        description "Node signaling address.";
      }
      leaf-list flag {
        type flag-type;
        description "Node operational flags.";
      }      
      leaf is-abstract {
        type boolean;
        description 
          "true if the node is abstract, false when the node is
          actual.";
      }
      container underlay-topology {
        if-feature te-topology-hierarchy;
        description 
          "When an abstract node encapsulates a topology, 
          the attributes in this container point to said topology.";
        leaf provider-id-ref {
          type leafref {
            path "/tet:te-topologies/tet:topology/tet:provider-id";
          }
          description
            "A reference to a provider-id.";
        }
        leaf client-id-ref {
          type leafref {
            path "/tet:te-topologies/tet:topology/tet:client-id";
          }
          description
            "A reference to a client-id.";
        }
        leaf topology-id-ref {
          type leafref {
            path "/tet:te-topologies/tet:topology"
              +"/tet:te-topology-id";
          }
          description
            "A reference to a te-topology-id.";
        }
      }
      leaf admin-status {
        type te-admin-status;
        description
          "The administrative state of the link.";
      }
      list connectivity-matrix {
        key "id";
        description
          "Represents node's switching limitations, i.e. limitations
           in interconnecting network TE links across the node.";
        leaf id {
          type uint32;
          description "Identifies the connectivity-matrix entry.";
        }
        container from-link {
          uses tet:link-end-ref;
          description 
            "Reference to source NTP.";
        }
        container to-link {
          uses tet:link-end-ref;
          description 
            "Reference to destination NTP.";
        }
        leaf is-allowed {
          type boolean;
          description
            "true  - switching is allowed, 
             false - switching is disallowed.";
        }
      }
    }
    list te-link {
      key "te-link-id";
      description
        "The local representation of a TE link, which
        interconnect TE nodes.";
      leaf te-link-id {
        type te-link-id;
        description
          "TE link identifier.";
      }
      choice stack-level {
        description 
          "The TE link can be partitioned into bundled
          links, or component links.";
        case bundle {
          container bundled-links {
            description
              "A set of bundled links";
            list bundled-link {
              key "sequence";
              description
                "Specify a bundled interface that is
                further partitioned.";
              leaf sequence {
                type uint32;
                description
                  "Identify the sequence in the bundle.";
              }
              leaf te-link-ref {
                type leafref {
                  path "../../../te-link-id";
                  require-instance true;
                }
                description
                  "Reference to TE link on this node.";
              }
            }
          }
        }
        case component {
          container component-links {
            description
              "A set of component links";
            list component-link {
              key "sequence";
              description
                "Specify a component interface that is
                sufficient to unambiguously identify the
                appropriate resources";
                
              leaf sequence {
                type uint32;
                description
                  "Identify the sequence in the bundle.";
              }
              leaf component-link-ref {
                type leafref {
                  path "/if:interfaces/if:interface/if:name";
                  require-instance false;
                }
                description
                  "Reference to component link on this
                  node.";
              }
            }
          }
        }
      }
    }
  } // te-node-attributes
    
  grouping te-node-state-attributes {
    description "Node state attributes in a TE topology.";
    container te-node-state {
      description "Node state attributes in a TE topology.";
      uses information-source-attributes;
    }
  } // te-node-state-attributes

  grouping te-link-underlay-attributes {
    description "Attributes for  te-link underlay.";
    container underlay-primary-path {
      description 
        "The service path on the underlay topology that
         supports this link.";
      leaf provider-id-ref {
        type leafref {
          path "/tet:te-topologies/tet:topology/tet:provider-id";
          require-instance false;
        }
        description
          "A reference to a provider-id.";
      }
      leaf client-id-ref {
        type leafref {
          path "/tet:te-topologies/tet:topology/tet:client-id";
          require-instance false;
        }
        description
          "A reference to a client-id.";
      }
      leaf topology-id-ref {
        type leafref {
          path "/tet:te-topologies/tet:topology/tet:te-topology-id";
          require-instance false;
        }
        description 
          "Identifies the topology where the path belongs.";
      }
      list path-element {
        key "path-element-id";
        description 
          "A list of path elements describing the service path";
        leaf path-element-id {
          type uint32;
          description "To identify the element in a path.";
        }
        uses te-path-element;
      }
    } // underlay-primary-path
    list underlay-backup-path {
      key "index";
      description 
        "A list of backup service paths on the underlay topology that
        protect the underlay primary path. If the primary path is
        not protected, the list contains zero elements. If the 
        primary path is protected, the list contains one or more
        elements.";
      leaf index {
        type uint32;
        description
          "A sequence number to identify a backup path.";
      }
      leaf provider-id-ref {
        type leafref {
          path "/tet:te-topologies/tet:topology/tet:provider-id";
          require-instance false;
        }
        description
          "A reference to a provider-id.";
      }
      leaf client-id-ref {
        type leafref {
          path "/tet:te-topologies/tet:topology/tet:client-id";
          require-instance false;
        }
        description
          "A reference to a client-id.";
      }
      leaf topology-id-ref {
        type leafref {
          path "/tet:te-topologies/tet:topology/tet:te-topology-id";
          require-instance false;
        }
        description 
          "Identifies the topology where the path belongs.";
      }
      list path-element {
        key "path-element-id";
        description 
          "A list of path elements describing the backup service 
           path";
        leaf path-element-id {
          type uint32;
          description "To identify the element in a path.";
        }
        uses te-path-element;
      }
    } // underlay-backup-path
    leaf underlay-protection-type {
      type uint16;
      description
        "Underlay protection type desired for this link";
    }
    container underlay-trail-src {
      uses tet:link-end-ref;
      description
        "Source TE link of the underlay trail.";
    }
    container underlay-trail-des {
      uses tet:link-end-ref;
      description
        "Destination TE link of the underlay trail.";
    }
    container recovery {
	description
          "Status of the recovery process.";
        leaf restoration-status {
          type te-recovery-status;
          description
            "Restoration status.";
        }
        leaf protection-status {
          type te-recovery-status;
          description
            "Protection status.";
        }      
      }

  } // te-link-underlay-attributes

  grouping te-link-state-underlay-attributes {
    description "State attributes for te-link underlay.";
    leaf dynamic {
      type boolean;
      description 
        "true if the underlay is dynamically created.";
    }
    leaf committed {
      type boolean;
      description 
        "true if the underlay is committed.";
    }
  } // te-link-state-underlay-attributes
    
  grouping performance-metric-attributes {
    description
      "Link performance information in real time.";
    reference 
      "draft-ietf-ospf-te-metric-extensions.";
    leaf unidirectional-delay {
      type uint32 {
        range 0..16777215;
      }
      description "Delay or latency in micro seconds.";
    }
    leaf unidirectional-min-delay {
      type uint32 {
        range 0..16777215;
      }
      description "Minimum delay or latency in micro seconds.";
    }
    leaf unidirectional-max-delay {
      type uint32 {
        range 0..16777215;
      }
      description "Maximum delay or latency in micro seconds.";
    }
    leaf unidirectional-delay-variation {
      type uint32 {
        range 0..16777215;
      }
      description "Delay variation in micro seconds.";
    }
    leaf unidirectional-packet-loss {
      type decimal64 {
        fraction-digits 6;
        range "0 .. 50.331642";
      }
      description 
        "Packet loss as a percentage of the total traffic sent
        over a configurable interval. The finest precision is
        0.000003%.";
    }
    leaf unidirectional-residual-bandwidth {
      type decimal64 {
        fraction-digits 2;
      }
      description 
        "Residual bandwidth that subtracts tunnel
        reservations from Maximum Bandwidth (or link capacity)
        [RFC3630] and provides an aggregated remainder across QoS
        classes.";
    }
    leaf unidirectional-available-bandwidth {
      type decimal64 {
        fraction-digits 2;
      }
      description 
        "Available bandwidth that is defined to be residual
        bandwidth minus the measured bandwidth used for the
        actual forwarding of non-RSVP-TE LSP packets.  For a
        bundled link, available bandwidth is defined to be the
        sum of the component link available bandwidths.";
    }
    leaf unidirectional-utilized-bandwidth {
      type decimal64 {
        fraction-digits 2;
      }
      description
        "Bandwidth utilization that represents the actual
        utilization of the link (i.e. as measured in the router).
        For a bundled link, bandwidth utilization is defined to
        be the sum of the component link bandwidth
        utilizations.";
    }
  } // performance-metric-attributes

  grouping performance-metric-normality-attributes {
    description
      "Link performance metric normality attributes.";
    reference 
      "draft-ietf-ospf-te-metric-extensions.";
    leaf unidirectional-delay {
      type performance-metric-normality;
      description "Delay normality.";
    }
    leaf unidirectional-min-delay {
      type performance-metric-normality;
      description "Minimum delay or latency normality.";
    }
    leaf unidirectional-max-delay {
      type performance-metric-normality;
      description "Maximum delay or latency normality.";
    }
    leaf unidirectional-delay-variation {
      type performance-metric-normality;
      description "Delay variation normality.";
    }
    leaf unidirectional-packet-loss {
      type performance-metric-normality;
      description "Packet loss normality.";
    }
    leaf unidirectional-residual-bandwidth {
      type performance-metric-normality;
      description "Residual bandwidth normality.";
    }
    leaf unidirectional-available-bandwidth {
      type performance-metric-normality;
      description "Available bandwidth normality.";
    }
    leaf unidirectional-utilized-bandwidth {
      type performance-metric-normality;
      description "Bandwidth utilization normality.";
    }
  } // performance-metric-normality-attributes

  grouping performance-metric-throttle-container {
    description
      "A container controlling performance metric throttle.";
    container performance-metric-throttle {
      if-feature te-performance-metric;
      must "suppression-interval >= measure-interval" {
        error-message 
          "suppression-interval cannot be less then 
            measure-interval";
        description
          "Constraint on suppression-interval and 
            measure-interval.";
      }
      description
        "Link performance information in real time.";
      reference 
        "draft-ietf-ospf-te-metric-extensions.";
      leaf unidirectional-delay-offset {
        type uint32 {
          range 0..16777215;
        }
        description 
          "Offset value to be added to the measured delay value.";
      }
      leaf measure-interval {
        type uint32;
        default 30;
        description 
          "Interval in seconds to measure the extended metric
          values.";
      }
      leaf advertisement-interval {
        type uint32;
        description 
          "Interval in seconds to advertise the extended metric
          values.";
      }
      leaf suppression-interval {
        type uint32 {
          range "1 .. max";
        }
        default 120;
        description 
          "Interval in seconds to suppress advertising the extended
          metric values.";
      }
      container threshold-out {
        uses performance-metric-attributes;
        description
          "If the measured parameter falls outside an upper bound
          for all but the min delay metric (or lower bound for
          min-delay metric only) and the advertised value is not
          already outside that bound, anomalous announcement will be
          triggered.";
      }
      container threshold-in {
        uses performance-metric-attributes;
        description
          "If the measured parameter falls inside an upper bound
          for all but the min delay metric (or lower bound for
          min-delay metric only) and the advertised value is not
          already inside that bound, normal (anomalous-flag cleared)
          announcement will be triggered.";
      }
      container threshold-accelerated-advertisement {
        description
          "When the difference between the last advertised value and
          current measured value exceed this threshold, anomalous
          announcement will be triggered.";
        uses performance-metric-attributes;
      }
    }
  } // performance-metric-throttle-container

  grouping te-link-info-attributes {
    description
      "Advertised TE information attributes.";
    leaf link-index {
      type uint64;
      description
        "The link identifier.  If OSPF is used, this represents an
        ospfLsdbID.  If IS-IS is used, this represents an isisLSPID.
        If a locally configured link is used, this object represents
        a unique value, which is locally defined in a router.";
    }
    leaf administrative-group {
      type te-types:admin-groups;
      description
        "Administrative group or color of the link. 
        This attribute covers both administrative group (defined in
        RFC3630, RFC5329, and RFC5305), and extended administrative
        group (defined in RFC7308).";
    }
    leaf max-link-bandwidth {
      type decimal64 {
        fraction-digits 2;
      }
      description
        "Maximum bandwidth that can be seen on this link in this
        direction. Units in bytes per second";
    }
    leaf max-resv-link-bandwidth {
      type decimal64 {
        fraction-digits 2;
      }
      description
        "Maximum amount of bandwidth that can be reserved in this
         direction in this link. Units in bytes per second";
    }
    list unreserved-bandwidth {
      key "priority";
      max-elements "8";
      description
        "Unreserved bandwidth for 0-7 priority levels. Units in
        bytes per second";
      leaf priority {
        type uint8 {
          range "0..7";
        }
        description "Priority";
      }
      leaf bandwidth {
        type decimal64 {
          fraction-digits 2;
        }
        description
          "Unreserved bandwidth for this level";
      }
    }
    leaf te-default-metric {
      type uint32;
      description
        "Traffic Engineering Metric";
    }
    container performance-metric {
      if-feature te-performance-metric;
      description
        "Link performance information in real time.";
      reference 
        "draft-ietf-ospf-te-metric-extensions.";
      container measurement {
        description
          "Measured performance metric values. Static configuration
          and manual overrides of these measurements are also 
          allowed.";
        uses performance-metric-attributes;
      }
      container normality
      {
        description
          "Performance metric normality values.";
        uses performance-metric-normality-attributes;
      }
    }
    leaf link-protection-type {
      type enumeration {
        enum "unprotected" {
          description "unprotected";
        }
        enum "extra-traffic" {
          description "Extra traffic";
        }
        enum "shared" {
          description "Shared";
        }
        enum "1-for-1" {
          description "One for one protection";
        }
        enum "1-plus-1" {
          description "One plus one protection";
        }
        enum "enhanced" {
          description "Enhanced protection";
        }
      }
      description
        "Link Protection Type desired for this link";
    }
    list interface-switching-capabilities {
      key "switching-capability";
      description
        "List of interface capabilities for this interface";
      leaf switching-capability {
        type identityref {
          base te-types:switching-capabilities;
        }
        description
          "Switching Capability for this interface";
      }
      leaf encoding {
        type identityref {
          base te-types:lsp-encoding-types;
        }
        description
          "Encoding supported by this interface";
      }
      list max-lsp-bandwidth {
        key "priority";
        max-elements "8";
        description
          "Maximum LSP Bandwidth at priorities 0-7";
        leaf priority {
          type uint8 {
            range "0..7";
          }
          description "Priority";
        }
        leaf bandwidth {
          type decimal64 {
            fraction-digits 2;
          }
          description
            "Max LSP Bandwidth for this level";
        }
      }
      container packet-switch-capable {
        when "../switching-capability = 'PSC-1'  or "
          +"../switching-capability = 'PSC-2' or "
          +"../switching-capability = 'PSC-3' or "
          +"../switching-capability = 'PSC-4'" {
          description "Valid only for PSC";
        }
        description
          "Interface has packet-switching capabilities";
        leaf minimum-lsp-bandwidth {
          type decimal64 {
            fraction-digits 2;
          }
          description
            "Minimum LSP Bandwidth. Units in bytes per second";
        }
        leaf interface-mtu {
          type uint16;
          description
            "Interface MTU";
        }
      }
      container time-division-multiplex-capable {
        when "../switching-capability = 'TDM'" {
          description "Valid only for TDM";
        }
        description
          "Interface has time-division multiplex capabilities";

        leaf minimum-lsp-bandwidth {
          type decimal64 {
            fraction-digits 2;
          }
          description
            "Minimum LSP Bandwidth. Units in bytes per second";
        }
        leaf indication {
          type enumeration {
            enum "standard" {
              description "Indicates support of standard SONET/SDH";
            }
            enum "arbitrary" {
              description "Indicates support of arbitrary SONET/SDH";
            }
          }
          description
            "Indication whether the interface supports Standard or
             Arbitrary SONET/SDH";
        }
      }
    }
    container te-srlgs {
      description
        "A list of SLRGs.";
      leaf-list values {
        type te-types:srlg;
        description "SRLG value";
      }
    }
  } // te-link-info-attributes

  grouping te-link-attributes {
    description 
      "Link attributes in a TE topology.";
    container te-link-attributes {
      description "Link attributes in a TE topology.";
      uses config-schedule-attributes;
      leaf name {
        type string;
        description "Link Name";
      }
      leaf-list flag {
        type flag-type;
        description "Link flags";
      }
      leaf is-abstract {
        type boolean;
        description "true if the link is abstract.";
      }
      container underlay {
        if-feature te-topology-hierarchy;
        presence 
          "Indicates the underlay exists for this link.";
        description "State of the underlay of this link.";

        uses te-link-underlay-attributes;
      } // underlay
      leaf admin-status {
        type te-admin-status;
        description
          "The administrative state of the link.";
      }
      uses performance-metric-throttle-container;
      uses te-link-info-attributes;
    }
  } // te-link-attributes

  grouping te-link-state-attributes {
    description 
      "Link state attributes in a TE topology.";
    container te-link-state {
      description "Link state attributes in a TE topology.";
      leaf oper-status {
        type enumeration {
          enum up {
            value 1;
            description
            "Operational up";
          }
          enum down {
            value 2;
            description
            "Operational down.";
          }
          enum testing {
            value 3;
            description
            "In some test mode";
          }
          enum unknown {
            value 4;
            description
            "Status cannot be determined for some reason.";
          }
        }
        description
          "The current operational state of the link.";
      }
      uses information-source-attributes;
      list alt-information-sources {
        key "information-source";
        description
          "A list of information sources learned but not used.";
        uses information-source-attributes;
        uses te-link-info-attributes;
      }
      container recovery {
        description
          "Status of the recovery process.";
        leaf restoration-status {
          type te-recovery-status;
          description
            "Restoration status.";
        }
        leaf protection-status {
          type te-recovery-status;
          description
            "Protection status.";
        }      
      }
    }
  } // te-link-state-attributes

  grouping template-attributes {
    description 
      "Common attributes for all templates.";

    leaf priority {
      type uint16;
      description
        "The preference value to resolve conflicts between different
        templates. When two or more templates specify values for 
        one configuration attribute, the value from the template
        with the highest priority is used.";
    }
    leaf reference-change-policy {
      type enumeration {
        enum no-action {
          description
            "When an attribute changes in this template, the 
            configuration node referring to this template does 
            not take any action.";
        }
        enum not-allowed {
          description
            "When any configuration object has a reference to this
            template, changing this template is not allowed.";
        }
        enum cascade {
          description
            "When an attribute changes in this template, the 
            configuration object referring to this template applies
            the new attribute value to the corresponding 
            configuration.";
        }
      }
      description
        "This attribute specifies the action taken to a configuration
        node that has a reference to this template.";
    }
  } // template-attributes

  /*
   * Configuration data nodes
   */

  container te-topologies {
    description
      "This container acts as the top-level data element of 
       configuration data.";
    list topology {
      key "provider-id client-id te-topology-id";
      description
        "This is the model of an abstract topology. A topology
        contains nodes and links. Each topology MUST be identified
        by a unique te-topology-id for reason that a network could
        contain many topologies.";
      leaf provider-id {
        type te-global-id;
        description
          "An identifier to uniquely identify a provider.";
      }
      leaf client-id {
        type te-global-id;
        description
          "An identifier to uniquely identify a client.";
      }
      leaf te-topology-id {
        type te-topology-id;
        description
          "It is presumed that a datastore will contain many
          topologies. To distinguish between topologies it is
          vital to have UNIQUE topology identifiers.";
      }
      uses config-schedule-attributes;
      container topology-types {
        description
          "This container is used to identify the type, or types (as
          a topology can support several types simultaneously), of
          the topology.
          Topology types are the subject of several integrity
          constraints that an implementing server can validate in
          order to maintain integrity of the datastore.
          Topology types are indicated through separate data nodes;
          the set of topology types is expected to increase over
          time.
          To add support for a new topology, an augmenting module
          needs to augment this container with a new empty optional
          container to indicate the new topology type.
          The use of a container allows to indicate a
          subcategorization of topology types.
          The container SHALL NOT be augmented with any data nodes
          that serve a purpose other than identifying a particular
          topology type.";
        uses te-topology-type; // Defines the TE topology type.
      }
      list node {
        key "te-node-id";
        leaf te-node-id {
          type te-node-id;
          description
            "The identifier of a node in the topology.
            A node is specific to a topology to which it belongs.";
        }
        description
          "The list of network nodes defined for the topology.";
        leaf te-node-template {
          if-feature template;
          type leafref {
            path "/te-topologies/node-template/name";
          }
          description
            "The reference to a TE node template.";
        }
        uses te-node-attributes;
      }
      list link {
        key "source-te-node-id source-te-link-id "
          + "dest-te-node-id dest-te-link-id";
        leaf source-te-node-id {
          type leafref {
            path "../../node/te-node-id";
          }
          mandatory true;
          description
            "Source node identifier, must be in same topology.";
        }
        leaf source-te-link-id {
          type leafref {
            path "../../node[te-node-id = "
              + "current()/../source-te-node-id]/"
              + "te-link/te-link-id";
          }
          mandatory true;
          description
            "Source TE link identifier, must be in same topology.";
        }
        leaf dest-te-node-id {
          type leafref {
            path "../../node/te-node-id";
          }
          mandatory true;
          description
            "Destination node identifier, must be in the same
            topology.";
        }
        leaf dest-te-link-id {
          type leafref {
            path "../../node[te-node-id = "
              + "current()/../dest-te-node-id]/"
              + "te-link/te-link-id";
          }
          mandatory true;
          description
            "Destination TE link identifier, must be in same
            topology.";
        }
        description
          "TE link is a logical construct that represents a way
          to group/map information about certain physical
          resources (and their properties) that interconnect TE
          nodes.
          A Network Link connects a by Local (Source) node and
          a Remote (Destination) Network Nodes via a set of the
          nodes' TE links.
          As it is possible to have several links between the
          same source and destination nodes, and as a link
          could potentially be re-homed, to ensure that we
          would always know to distinguish between
          links, every link is identified by a dedicated link
          identifier.
          Note that a link models a point-to-point link, not a
          multipoint link.";
        leaf te-link-template {
          if-feature template;
          type leafref {
            path "/te-topologies/link-template/name";
          }
          description
            "The reference to a TE link template.";
        }
        uses te-link-attributes;
      } // link
    } // topology

    list node-template {
      if-feature template;
      key "name";
      leaf name {
        type te-template-name;
        description
          "The name to identify a TE node template.";
      }
      description
        "The list of TE node templates used to define sharable
        and reusable TE node attributes.";
      uses template-attributes;
      leaf-list te-node-template {
        type leafref {
          path "/te-topologies/node-template/name";
        }
        description
          "The reference to a TE node template.";
      }
      uses te-node-attributes;
    } // node

    list link-template {
      if-feature template;
      key "name";
      leaf name {
        type te-template-name;
        description
          "The name to identify a TE link template.";
      }
      description
        "The list of TE link templates used to define sharable
        and reusable TE link attributes.";
      uses template-attributes;
      leaf-list te-link-template {
        type leafref {
          path "/te-topologies/link-template/name";
        }
        description
          "The reference to a TE link template.";
      }
      uses te-link-attributes;
    } // link
  } // te-topologies

  /*
   * Operational state data nodes
   */

  container te-topologies-state {
    config false;
    description
      "This container acts as the top-level state data element of 
       operational data.";
    list topology {
      key "provider-id client-id te-topology-id";
      description
        "This is the model of an abstract topology. A topology
        contains nodes and links. Each topology MUST be identified
        by a unique te-topology-id for reason that a network could
        contain many topologies.";
      leaf provider-id {
        type te-global-id;
        description
          "An identifier to uniquely identify a provider.";
      }
      leaf client-id {
        type te-global-id;
        description
          "An identifier to uniquely identify a client.";
      }
      leaf te-topology-id {
        type te-topology-id;
        description
          "It is presumed that a datastore will contain many
          topologies. To distinguish between topologies it is
          vital to have UNIQUE topology identifiers.";
      }
      leaf server-provided {
        type boolean;
        config false;
        description
          "Indicates whether the topology is configurable by clients,
          or whether it is provided by the server.  This leaf is
          populated by the server implementing the model.
          It is set to false for topologies that are created by a
          client; it is set to true otherwise.  If it is set to true,
          any attempt to edit the topology MUST be rejected.";
      }
      container topology-types {
        description
          "This container is used to identify the type, or types (as
          a topology can support several types simultaneously), of
          the topology.
          Topology types are the subject of several integrity
          constraints that an implementing server can validate in
          order to maintain integrity of the datastore.
          Topology types are indicated through separate data nodes;
          the set of topology types is expected to increase over
          time.
          To add support for a new topology, an augmenting module
          needs to augment this container with a new empty optional
          container to indicate the new topology type.
          The use of a container allows to indicate a
          subcategorization of topology types.
          The container SHALL NOT be augmented with any data nodes
          that serve a purpose other than identifying a particular
          topology type.";
        uses te-topology-type; // Defines the TE topology type.
      }
      list node {
        key "te-node-id";
        leaf te-node-id {
          type te-node-id;
          description
            "The identifier of a node in the topology.
            A node is specific to a topology to which it belongs.";
        }
        description
          "The list of network nodes defined for the topology.";
        leaf te-node-template {
          if-feature template;
          type leafref {
            path "/te-topologies/node-template/name";
          }
          description
            "The reference to a TE node template.";
        }
        uses te-node-attributes;
        uses te-node-state-attributes;
      }
      list link {
        key "source-te-node-id source-te-link-id "
          + "dest-te-node-id dest-te-link-id";
        leaf source-te-node-id {
          type leafref {
            path "../../node/te-node-id";
          }
          mandatory true;
          description
            "Source node identifier, must be in same topology.";
        }
        leaf source-te-link-id {
          type leafref {
            path "../../node[te-node-id = "
              + "current()/../source-te-node-id]/"
              + "te-link/te-link-id";
          }
          mandatory true;
          description
            "Source TE link identifier, must be in same topology.";
        }
        leaf dest-te-node-id {
          type leafref {
            path "../../node/te-node-id";
          }
          mandatory true;
          description
            "Destination node identifier, must be in the same
            topology.";
        }
        leaf dest-te-link-id {
          type leafref {
            path "../../node[te-node-id = "
              + "current()/../dest-te-node-id]/"
              + "te-link/te-link-id";
          }
          mandatory true;
          description
            "Destination TE link identifier, must be in same
            topology.";
        }
        description
          "TE link is a logical construct that represents a way
          to group/map information about certain physical
          resources (and their properties) that interconnect TE
          nodes.
          A Network Link connects a by Local (Source) node and
          a Remote (Destination) Network Nodes via a set of the
          nodes' TE links.
          As it is possible to have several links between the
          same source and destination nodes, and as a link
          could potentially be re-homed, to ensure that we
          would always know to distinguish between
          links, every link is identified by a dedicated link
          identifier.
          Note that a link models a point-to-point link, not a
          multipoint link.";
        leaf te-link-template {
          if-feature template;
          type leafref {
            path "/te-topologies/link-template/name";
          }
          description
            "The reference to a TE link template.";
        }
        uses te-link-attributes;
        uses te-link-state-attributes;
      } // link
    } // topology
  } // te-topologies

  augment "/te-topologies-state/topology/link/te-link-attributes/"
    + "underlay" {
    description "Add state attributes to te-link underlay.";
    uses te-link-state-underlay-attributes;
  }

  /*
   * Notifications
   */

  notification te-node-event {
    description "Notification event for TE node";
    leaf event-type {
      type te-topology-event-type;
      description "Event type";
    }
    uses node-ref;
    uses te-topology-type;
    uses tet:te-node-attributes;
    uses tet:te-node-state-attributes;
  }
  
  notification te-link-event {
    description "Notification event for TE link";
    leaf event-type {
      type te-topology-event-type;
      description "Event type";
    }
    uses link-ref;
    uses te-topology-type;
    uses tet:te-link-attributes;
    uses tet:te-link-state-attributes;
  }

  augment "/te-link-event/te-link-attributes/underlay" {
    description "Add state attributes to te-link underlay.";
    uses te-link-state-underlay-attributes;
  }
}
